; 3D of 3 point circle center

(defun pointminus (p1 p0 / dx dy dz pm)
 (setq dx (- (car p1) (car p0)))
 (setq dy (- (cadr p1) (cadr p0)))
 (setq dz (- (caddr p1) (caddr p0)))
 (setq pm (list dx dy dz))
)

(defun pointplus (p1 p0 / dx dy dz pp)
 (setq dx (+ (car p1) (car p0)))
 (setq dy (+ (cadr p1) (cadr p0)))
 (setq dz (+ (caddr p1) (caddr p0)))
 (setq pp (list dx dy dz))
)

(defun point3mean (p1 p2 p3 / x y z pm)
 (setq x (/ (+ (car p1) (car p2) (car p3)) 3))
 (setq y (/ (+ (cadr p1) (cadr p2) (cadr p3)) 3))
 (setq z (/ (+ (caddr p1) (caddr p2) (caddr p3)) 3))
 (setq pm (list x y z))
)

(defun linegrad (p1 p2 / l pm gx gy gz g)
 (setq l (distance p1 p2))
 (setq pm (pointminus p2 p1))
 (setq gx (/ (car pm) l))
 (setq gy (/ (cadr pm) l))
 (setq gz (/ (caddr pm) l))
 (setq g (list gx gy gz))
)

(defun linepk (g p / dx dy dz pk)
 (setq dx (* (car g) (car p)))
 (setq dy (* (cadr g) (cadr p)))
 (setq dz (* (caddr g) (caddr p)))
 (setq pk (+ dx dy dz))
)

(defun pointpk (g l / dx dy dz pk)
 (setq dx (* (car g) l))
 (setq dy (* (cadr g) l))
 (setq dz (* (caddr g) l))
 (setq pk (list dx dy dz))
)

(defun circlecenter3p (p1 p2 p3 / a1 a2 b1 b2 s1 s2 t1 t2 c1 c2 ab bc lc dc c)
 (setq a1 (- (car p2) (car p1)))
 (setq a2 (- (car p3) (car p2)))
 (setq b1 (- (cadr p2) (cadr p1)))
 (setq b2 (- (cadr p3) (cadr p2)))
 (setq s1 (/ (+ (car p2) (car p1)) 2))
 (setq s2 (/ (+ (car p3) (car p2)) 2))
 (setq t1 (/ (+ (cadr p2) (cadr p1)) 2))
 (setq t2 (/ (+ (cadr p3) (cadr p2)) 2))
 (setq c1 (- 0 (+ (* a1 s1) (* b1 t1))))
 (setq c2 (- 0 (+ (* a2 s2) (* b2 t2))))
 (setq ab (- (* b1 a2) (* b2 a1)))
 (setq bc (- (* b2 c1) (* b1 c2)))
 (setq lc (/ bc ab))
 (setq dc (/ (- 0 (+ c1 (* a1 lc))) b1))
 (setq c (list lc dc 0))
)

(defun c:3D3PCC (/ p1 p2 p3)
 (setq p1 (getpoint "Circle point #1: "))
 (setq p2 (getpoint "Circle point #2: "))
 (setq p3 (getpoint "Circle point #3: "))

 (setq p01 (list 0 0 0))
 (setq p02 (pointminus p2 p1))
 (setq p03 (pointminus p3 p1))
 (setq pm (point3mean p01 p02 p03))
 (setq gl (linegrad p01 pm))
 (setq lm2 (linepk gl p02))
 (setq lm3 (linepk gl p03))
 (setq pp2 (pointpk gl lm2))
 (setq pp3 (pointpk gl lm3))
 (setq pd2 (pointminus p02 pp2))
 (setq pd3 (pointminus p03 pp3))
 (setq pd (pointminus pd2 pd3))
 (setq gd (linegrad p01 pd))
 (setq dm2 (linepk gd pd2))
 (setq dm3 (linepk gd pd3))
 (setq pc1 (list 0 0 0))
 (setq pc2 (list lm2 dm2 0))
 (setq pc3 (list lm3 dm3 0))
 (setq c (circlecenter3p pc1 pc2 pc3))
 (setq pcl (pointpk gl (car c)))
 (setq pcd (pointpk gd (cadr c)))
 (setq p0c (pointplus pcl pcd))
 (setq pc (pointplus p0c p1))
 (setq r (distance pc p1))

 (command "_point" pc)
 (command "_circle" pc r)
 (princ pc)
 (princ)
; (command "_ellipse" "_C" pc p1 p2)
)
