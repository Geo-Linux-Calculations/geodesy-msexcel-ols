;;; \U+0412\U+044B\U+043D\U+043E\U+0441\U+043A\U+0430 \U+0441 \U+0434\U+043B\U+0438\U+043D\U+043E\U+0439/\U+043F\U+043B\U+043E\U+0449\U+0430\U+0434\U+044C\U+044E \U+043B\U+0438\U+043D\U+0438\U+0438
;;; http://geodesist.ru/members/1958.30261/
;;; 03 apr 2021.
(defun c:plcallout (/ tm o p c l a s)
 (vl-load-com)
 (setq old_d (getvar "DYNMODE"))
 (setvar "DYNMODE" 1)
 (setq txsel "\U+0412\U+0430\U+0448 \U+0432\U+044B\U+0431\U+043E\U+0440")
 (setq txobj "\U+0423\U+043A\U+0430\U+0436\U+0438\U+0442\U+0435 \U+043B\U+0438\U+043D\U+0438\U+044E:")
 (setq txl "\U+0414\U+041B\U+0418\U+041D\U+0410")
 (setq txa "\U+041F\U+041B\U+041E\U+0429\U+0410\U+0414\U+042C")
 (setq txla "\U+041E\U+0411\U+0410")
 (setq txga "\U+0413\U+0415\U+041A\U+0422\U+0410\U+0420\U+042B")
 (setq txm "\U+043C")
 (setq txsq "\U+00B2")
 (setq txag "\U+0433\U+0430")
 (initget 1 (strcat txl " " txa " " txla " " txga))
 (setq tm (strcase (getkword (strcat txsel " <" txl "/" txa "/" txla "/" txga ">: ")))
       o  (entsel txobj)
       p  (cadr o)
       c  (vlax-ename->vla-object (car o))
       l  (cond ((or (eq tm txl) (eq tm txla)) (vla-get-length c)) (t 0))
       a  (cond ((or (eq tm txa) (eq tm txla) (eq tm txga)) (vla-get-area c)) (t nil))
 )
 (setq s (cond ((eq tm txl) (strcat "L = " (rtos l 2 3) " " txm))
               ((eq tm txa) (strcat "S = " (rtos a 2 2) " " txm txsq))
               ((eq tm txla) (strcat "L = " (rtos l 2 3) " " txm "\nS = " (rtos a 2 2) " " txm txsq))
               ((eq tm txga) (strcat "S = " (rtos (/ a 10000) 2 2) " " txag))
               (t nil)
         )
 )
 (vl-cmdf "_leader" p pause "" s "")
 (setvar "DYNMODE" old_d)
 (princ)
)

 ;|«Visual LISP© Format Options»
(100 1 2 2 nil " " 80 60 0 0 0 nil nil nil T)
;*** \U+041D\U+0415 \U+0434\U+043E\U+0431\U+0430\U+0432\U+043B\U+044F\U+0439\U+0442\U+0435 \U+0442\U+0435\U+043A\U+0441\U+0442 \U+043F\U+043E\U+0434 \U+043A\U+043E\U+043C\U+043C\U+0435\U+043D\U+0442\U+0430\U+0440\U+0438\U+044F\U+043C\U+0438! ***|;
