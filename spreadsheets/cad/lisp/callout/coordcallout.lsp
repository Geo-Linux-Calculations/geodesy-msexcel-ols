;coordcallout
(defun c:coordcallout (/ fz p xyz txy txn txq)
 (vl-load-com)
 (setq old_d (getvar "DYNMODE"))
 (setvar "DYNMODE" 1)
 (setq txy "\U+0414\U+0430")
 (setq txn "\U+041D\U+0435\U+0442")
 (setq txq "\U+041F\U+043E\U+0434\U+043F\U+0438\U+0441\U+044B\U+0432\U+0430\U+0442\U+044C")
 (initget (strcat txy " " txn " Lf Ytn _ Y N Y N"))
 (setq fz (getkword (strcat "\n" txq " Z [" txy "/" txn "] <" txn ">? : ")))
 (while (and (setq p (getpoint "\nPoint <Exit>")))
  (setq
       xyz (strcat "X=" (rtos (nth 1 p) 2 3)"\nY=" (rtos (nth 0 p) 2 3)
            (if (= fz "Y") (strcat "\nZ=" (rtos (nth 2 p) 2 3))
             ""
            ))
  )
  (vl-cmdf "_leader" p pause "" xyz "")
 )
 (setvar "DYNMODE" old_d)
 (princ)
)
(princ "\U+0412\U+044B\U+0437\U+043E\U+0432 \U+0444\U+0443\U+043D\U+043A\U+0446\U+0438\U+0438: coordcallout")
(princ)
